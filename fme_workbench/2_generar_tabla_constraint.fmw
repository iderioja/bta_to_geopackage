FME workspace 2_generar_tabla_constraint.fmw

Parameters:
- Hoja = 164-70

Note: Creamos la tabla gpkg_data_columns
SQLCreator_2
    FORMAT = SQLITE3
    SQL_STATEMENT:
      CREATE TABLE gpkg_data_columns (
        table_name TEXT NOT NULL,
        column_name TEXT NOT NULL,
        name TEXT,
        title TEXT,
        description TEXT,
        mime_type TEXT,
        constraint_name TEXT,
        CONSTRAINT pk_gdc PRIMARY KEY (table_name, column_name),
        CONSTRAINT fk_gdc_tn FOREIGN KEY (table_name) REFERENCES gpkg_contents(table_name)
      );
    DATASET = $(FME_MF_DIR_ENCODED)164-70.gpkg
    RESULT -> SQLCreator_2_Result
Note: Creamos la tabla gpkg_data_column_constraints
SQLCreator_3
    FORMAT = SQLITE3
    SQL_STATEMENT:
      CREATE TABLE gpkg_data_column_constraints (
        constraint_name TEXT NOT NULL,
        constraint_type TEXT NOT NULL,
        value TEXT,
        min NUMERIC,
        minIsInclusive BOOLEAN,
        max NUMERIC,
        maxIsInclusive BOOLEAN,
        description TEXT,
        CONSTRAINT gdcc_ntv UNIQUE (constraint_name, constraint_type, value)
      );
    DATASET = $(FME_MF_DIR_ENCODED)164-70.gpkg
    RESULT -> SQLCreator_2_Result
SQLCreator_2_Result: Logger
    MESSAGE = Feature is:
    MAXCOORDS = 20
    MAXFEATS = 20
