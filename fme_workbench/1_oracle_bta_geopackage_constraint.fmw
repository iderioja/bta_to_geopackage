FME workspace 1_oracle_bta_geopackage_constraint.fmw

Parameters:
- DestDataset_GEOPACKAGE =   # Destination GeoPackage File
- SourceDataset_SHAPE =   # Source Esri Shape File(s)
- Hoja = 164-70
- SourceDataset_ORACLE_SPATIAL_1 = iderioja   # Service Name or Easy Connect

Readers:
- ORACLE_SPATIAL_1: ORACLE_SPATIAL from $(SourceDataset_ORACLE_SPATIAL_1)
- SHAPE_1: SHAPE from $(SourceDataset_SHAPE)

Writers:
- GEOPACKAGE_1: GEOPACKAGE to $(DestDataset_GEOPACKAGE) in ETRS89.UTM-30N

Note: Creación y exportación del archivo de exportación Geopackage desde Oracle Spatial / Estructura BTA
Note: Tabla BTA con la estructura de la tabla: / Hidrografia_pun
Hidrografia_pun (reader SHAPE_1)
    attributes: id_fenomen char(17), id_tipo char(4), num_hoja char(13), angulo number(19,14), TIPO_0019 char(3), TIPO_0020 char(3), TIPO_0021 char(3), IDIOMA char(3), NOMBRE char(70)
Note: Oracle table: / IDERIOJA.IDE_BTA_HIDROGRAFIA_PUN_U89
IDERIOJA.IDE_BTA_HIDROGRAFIA_PUN_U89 (reader ORACLE_SPATIAL_1)
    attributes: ID_PUNTO number(38,0), CODIGO_FENOMENO varchar2(4), NOMBRE_FENOMENO varchar2(50), COLUMNA_FILA_HOJA_5000 varchar2(7), TEXTO_ASOCIADO varchar2(250), OBSERVACIONES varchar2(250), NOMBRE varchar2(4000), IDIOMA varchar2(4000), IDIOMA_ETIQUETA varchar2(4000), COMPONEN2D varchar2(4000), COMPONEN2D_ETIQUETA varchar2(4000), COMPONEN1D varchar2(4000), COMPONEN1D_ETIQUETA varchar2(4000), TIPO_0019 varchar2(4000), TIPO_0019_ETIQUETA varchar2(4000), TIPO_0020 varchar2(4000), TIPO_0020_ETIQUETA varchar2(4000), TIPO_0021 varchar2(4000), TIPO_0021_ETIQUETA varchar2(4000)
    -> AttributeRenamer
AttributeRenamer
    ATTR_LIST = ID_PUNTO,id_fenomen,,COLUMNA_FILA_HOJA_5000,num_hoja,,CODIGO_FENOMENO,id_tipo,
    -> hidrografia_pun (writer GEOPACKAGE_1)
Note: Sample feature table: / hidrografia_pun
hidrografia_pun (writer GEOPACKAGE_1)
    attributes: id_fenomen text(17), id_tipo text(4), num_hoja text(13), angulo double, NOMBRE text(70), IDIOMA text(3), TIPO_0019 text(3), TIPO_0020 text(3), TIPO_0021 text(3)
